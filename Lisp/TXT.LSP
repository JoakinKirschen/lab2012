(defun *ERROR* (st)
  (terpri)
  (princ "\nERROR: ")
  (princ st)
  (princ)
)

(defun waard ()
  (initget "Change Replace")
  (setq xx (getkword "\nChange/<Replace>: "))
  (cond	((= xx "Change") (waardc))
	((= xx "Replace") (waardv))
	((= xx nil) (waardv))
  )
  (princ)
)

(defun WIT ()
  (setq str (getstring "new Width ? "))
  (setq th (atof str))
  (if (/= telt 0)
    (progn
      (setq be 0)
      (while (< be telt)
	(setq ch (assoc 41 (setq e (entget (ssname txt be)))))
	(terpri)
	(setq e (subst (cons 41 th) ch e))
	(entmod e)
	(setq be (1+ be))
      )
    )
  )
  (terpri)
)

(defun waardv ()
  (setq str (getstring "new text ? " T))
  (if (/= telt 0)
    (progn
      (setq be 0)
      (while (< be telt)
	(setq ct (assoc 1 (setq e (entget (ssname txt be)))))
	(terpri)
	(setq e (subst (cons 1 str) ct e))
	(entmod e)
	(setq be (1+ be))
      )
    )
  )
  (terpri)
)

(defun waardc ()
  (if (/= telt 0)
    (progn
      (setq chm	0
	    p txt
      )
      (if p
	(progn
	  (setq cont t)
	  (while cont
	    (setq osl (strlen (setq os (getstring "\nOld text ? " t))))
	    (if	(= osl 0)
	      (princ "Null input invalid")
	      (setq cont nil)
	    )
	  )
	  (setq nsl (strlen (setq ns (getstring "\nNew text ? " t))))
	  (setq	l    0
		telt (sslength p)
	  )
	  (while (< l telt)
	    (if	(= "TEXT"
		   (cdr (assoc 0 (setq e (entget (ssname p l)))))
		)
	      (progn
		(setq chf nil
		      si  1
		)
		(setq s (cdr (setq as (assoc 1 e))))
		(setq otxt s)
		(while (= osl
			  (setq	sl (strlen
				     (setq st (substr s si osl))
				   )
			  )
		       )
		  (if (= st os)
		    (progn
		      (setq s (strcat (substr s 1 (1- si))
				      ns
				      (substr s (+ si osl))
			      )
		      )
		      (setq ntxt s)
		      (setq chf t)
		      (setq si (+ si nsl))
		    )
		    (setq si (1+ si))
		  )
		)
		(if chf
		  (progn
		    (setq e (subst (cons 1 s) as e))
		    (entmod e)
		    (princ "replaced ")
		    (princ otxt)
		    (princ " with ")
		    (princ ntxt)
		    (terpri)
		    (setq chm (1+ chm))
		  )
		)
	      )
	    )
	    (setq l (1+ l))
	  )
	)
      )
      (princ "Changed ")
      (princ chm)
      (princ " text lines.")
      (terpri)
    )
  )
  (terpri)
)

(defun hoog ()
  (setq str (getstring "new textheight ? "))
  (setq th (atof str))
  (if (/= telt 0)
    (progn
      (setq be 0)
      (while (< be telt)
	(setq ch (assoc 40 (setq e (entget (ssname txt be)))))
	(terpri)
	(setq e (subst (cons 40 th) ch e))
	(entmod e)
	(setq be (1+ be))
      )
    )
  )
  (terpri)
)

(defun stijl ()
  (setq stij (getstring "new textstyle ? "))
  (if (/= telt 0)
    (progn
      (command "style" stij stij "" "" "" "" "" "")
      (setq be 0)
      (while (< be telt)
	(setq cs (assoc 7 (setq e (entget (ssname txt be)))))
	(terpri)
	(setq e (subst (cons 7 stij) cs e))
	(entmod e)
	(setq be (1+ be))
      )
    )
  )
  (terpri)
)

(defun laag ()
  (setq newl (getstring "new layer ? "))
  (if (/= telt 0)
    (progn
      (setq be 0)
      (while (< be telt)
	(setq cl (assoc 8 (setq e (entget (ssname txt be)))))
	(terpri)
	(setq e (subst (cons 8 newl) cl e))
	(entmod e)
	(setq be (1+ be))
      )
    )
  )
  (terpri)
)

(DEFUN UCASE ()
  (INITGET "ON OFF")
  (SETQ XXX (GETKWORD "<ON>/OFF"))
  (IF (= XXX "OFF")
    (PROGN
      (LCASE)
    )
    (PROGN
      (CASE)
    )
  )
)
(defun lcase ()
  (if (/= telt 0)
    (progn
      (setq be 0)
      (while (< be telt)
	(setq cs (assoc 1 (setq e (entget (ssname txt be)))))
	(setq ns (strcase (CDR cs) T))
	(terpri)
	(setq e (subst (cons 1 ns) cs e))
	(entmod e)
	(setq be (1+ be))
      )
    )
  )
  (terpri)
)

(defun case ()
  (if (/= telt 0)
    (progn
      (setq be 0)
      (while (< be telt)
	(setq cs (assoc 1 (setq e (entget (ssname txt be)))))
	(setq ns (strcase (CDR cs)))
	(terpri)
	(setq e (subst (cons 1 ns) cs e))
	(entmod e)
	(setq be (1+ be))
      )
    )
  )
  (terpri)
)

(defun kleur ()
  (setq vnc (getstring "new color ? "))
  (if (/= (setq ncc (strcase vnc)) "BYLAYER")
    (setq nc (atoi vnc))
  )
  (if (= ncc "BYLAYER")
    (setq nc "BYLAYER")
  )
  (if (/= telt 0)
    (progn
      (setq be 0)
      (while (< be telt)
	(setq e (entget (ssname txt be)))
	(setq ee (cdar e))
	(terpri)
	(command "change" ee "" "p" "c" nc "")
	(setq be (1+ be))
      )
    )
  )
  (terpri)
)

(defun hoek ()
  (setq str (getstring "new texthoek ? "))
  (setq th (atof str))
  (if (/= telt 0)
    (progn
      (setq be 0)
      (while (< be telt)
	(setq ch (assoc 50 (setq e (entget (ssname txt be)))))
	(terpri)
	(setq e (subst (cons 50 th) ch e))
	(entmod e)
	(setq be (1+ be))
      )
    )
  )
  (terpri)
)

(defun global ()
  (setq	p   nil
	lij nil
  )
  (SETQ TXT "TEXT")
  (SETQ TX (CONS 0 TXT))
  (SETQ VWRD 0)
  (terpri)
  (SETQ STY (GETSTRING "STYLE    <*>"))
  (IF (and (/= STY "")
	   (/= STY nil)
	   (/= STY "*")
      )
    (PROGN
      (setq sty (strcat sty))
      (SETQ ST (CONS 7 STY))
      (SETQ VWRD (+ 1 VWRD))
    )
  )
  (SETQ LAY (GETSTRING "LAYER    <*>"))
  (IF (and (/= LAY "")
	   (/= LAY nil)
	   (/= LAY "*")
      )
    (PROGN
      (setq lay (strcat lay))
      (SETQ LA (CONS 8 LAY))
      (SETQ VWRD (+ 2 VWRD))
    )
  )
  (SETQ COL (GETSTRING "COLOR    <*>"))
  (IF (and (/= COL "")
	   (/= COL nil)
	   (/= COL "*")
      )
    (PROGN
      (SETQ COL (ATOI COL))
      (SETQ CO (CONS 62 COL))
      (SETQ VWRD (+ 4 VWRD))
    )
  )
  (COND	((= VWRD 0) (SETQ LIJ (list TX)))
	((= VWRD 1) (SETQ LIJ (list TX ST)))
	((= VWRD 2) (SETQ LIJ (list TX LA)))
	((= VWRD 3) (SETQ LIJ (LIST TX ST LA)))
	((= VWRD 4) (SETQ LIJ (list TX CO)))
	((= VWRD 5) (SETQ LIJ (LIST TX CO ST)))
	((= VWRD 6) (SETQ LIJ (LIST TX CO LA)))
	((= VWRD 7) (SETQ LIJ (LIST TX CO LA ST)))
  )
  (SETQ P (SSGET "X" LIJ))
  (if (/= p nil)
    (progn
      (SETQ TXT P)
      (SETQ TXN (SSLENGTH TXT))
      (NOTE)
      (KEUZE)
    )
  )
)

(defun selBU ()
  (setq p (ssget))
  (if (/= p nil)
    (progn
      (select)
    )
  )
)

(DEFUN NOTE ()
  (PRINC "\nSelected ")
  (PRINC txn)
  (PRINC " text lines.")
  (terpri)
)

(defun select ()
  (PROMPT "\nBuilding up text selection-set.")
  (setq txn 0)
  (if (/= p nil)
    (progn
      (setq txt (ssadd))
      (setq l 0
	    n (sslength p)
      )
      (while (< l n)
	(setq test (cdr (assoc 0 (setq e (entget (ssname p l))))))
	(if (= "TEXT" test)
	  (progn
	    (setq sst (cdr (assoc -1 e)))
	    (ssadd sst txt)
	    (setq txn (1+ txn))
	  )
	)
	(setq l (1+ l))
      )
      (if (/= txn 0 nil)
	(progn
	  (NOTE)
	  (keuze)
	)
      )
    )
  )
)

(defun keuze ()
  (initget "Value Height Rotatiehoek Style Layer Color Ucase Width")
  (setq telt txn)
  (prompt "\nWhat do you want to edit ?")
  (setq	xx (getkword
	     "\nValue/Height/Rotatiehoek/Style/Layer/Color/Ucase/Width: "
	   )
  )
  (cond	((= xx "Value") (waard))
	((= xx "Height") (hoog))
	((= xx "Rotatiehoek") (hoek))
	((= xx "Style") (stijl))
	((= xx "Layer") (laag))
	((= xx "Color") (kleur))
	((= xx "Ucase") (ucase))
	((= xx "Width") (WIT))
  )
  (princ)
)


(defun c:txt ()
  (setvar "cmdecho" 0)
  (command "undo" "mark")
  (initget "Global Selected")
  (prompt "\nEditing text : ")
  (setq xx (getkword "\n<Global> or Selected: "))
  (cond	((or
	   (= xx "Global")
	   (= xx nil)
	 )
	 (progn
	   (global)
	 )
	)
	((= xx "Selected") (selBU))
  )
  (princ)
)

(DEFUN Loaded ()
  (SETQ Loaded "......................")
)
