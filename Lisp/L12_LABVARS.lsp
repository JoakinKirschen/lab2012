;;-----[ Deze functie altijd laten staan]------------------------------------
(defun L12_LABVARS ()
(princ "L12_LABVARS is loaded")
(princ)
)

(defun c:labvars ()
(setvar "ACADLSPASDOC" 0)
(setvar "ACISOUTVER" 70)
(setvar "AFLAGS" 16)
(setvar "ANGBASE" 0)
(setvar "ANGDIR" 0)
(setvar "APBOX" 0)
(setvar "APERTURE" 14)
(setvar "ATTDIA" 1)
(setvar "ATTMODE" 1)
(setvar "ATTREQ" 1)
(setvar "AUDITCTL" 0)
(setvar "AUNITS" 0)
(setvar "AUPREC" 0)
(setvar "AUTOSNAP" 63)
(setvar "AUXSTAT" 0)
(setvar "AXISUNIT" '(0.0 0.0) )
(setvar "BACKGROUNDPLOT" 2)
(setvar "BACTIONCOLOR" "7")
(setvar "BDEPENDENCYHIGHLIGHT" 1)
(setvar "BGRIPOBJSIZE" 8)
(setvar "BINDTYPE" 0)
(setvar "BLIPMODE" 0)
(setvar "BPARAMETERCOLOR" "7")
(setvar "BPARAMETERSIZE" 12)
(setvar "BTMARKDISPLAY" 1)
(setvar "BVMODE" 0)
(setvar "CALCINPUT" 1)
(setvar "CECOLOR" "BYLAYER")
(setvar "CELTSCALE" 1)
(setvar "CELTYPE" "ByLayer")
(setvar "CELWEIGHT" -1)
(setvar "CHAMFERA" 0)
(setvar "CHAMFERB" 0)
(setvar "CHAMFERC" 0)
(setvar "CHAMFERD" 0)
(setvar "CHAMMODE" 0)
(setvar "CIRCLERAD" 0)
(setvar "CMDDIA" 1)
(setvar "CMDECHO" 1)
(setvar "CMDINPUTHISTORYMAX" 20)
(setvar "CMLJUST" 0)
(setvar "CMLSCALE" 20)
(setvar "CMLSTYLE" "STANDARD")
(setvar "COMPASS" 0)
(setvar "COORDS" 2)
(setvar "CTAB" "Model")
(setvar "CTABLESTYLE" "Standard")
(setvar "CURSORSIZE" 5)
(setvar "DCTCUST" "C:/Documents and Settings/JOKI/Application Data/Autodesk/AutoCAD 2008/R17.1/enu/support/sample.cus")
(setvar "DCTMAIN" "nld")
(setvar "DELOBJ" 1)
(setvar "DEMANDLOAD" 3)
(setvar "DIMADEC" 0)
(setvar "DIMALT" 0)
(setvar "DIMALTD" 3)
(setvar "DIMALTF" 0.0394)
(setvar "DIMALTRND" 0)
(setvar "DIMALTTD" 3)
(setvar "DIMALTTZ" 0)
(setvar "DIMALTU" 2)
(setvar "DIMALTZ" 0)
(setvar "DIMAPOST" "")
(setvar "DIMASSOC" 2)
(setvar "DIMASZ" 2.5)
(setvar "DIMATFIT" 3)
(setvar "DIMAUNIT" 0)
(setvar "DIMAZIN" 0)
(setvar "DIMCEN" 2.5)
(setvar "DIMCLRD" 0)
(setvar "DIMCLRE" 0)
(setvar "DIMCLRT" 0)
(setvar "DIMDEC" 2)
(setvar "DIMDLE" 0)
(setvar "DIMDLI" 3.75)
(setvar "DIMDSEP" ",")
(setvar "DIMEXE" 1.25)
(setvar "DIMEXO" 0.625)
(setvar "DIMFIT" 3)
(setvar "DIMFRAC" 0)
(setvar "DIMGAP" 0.625)
(setvar "DIMJUST" 0)
(setvar "DIMLFAC" 1)
(setvar "DIMLIM" 0)
(setvar "DIMLUNIT" 2)
(setvar "DIMLWD" -2)
(setvar "DIMLWE" -2)
(setvar "DIMPOST" "")
(setvar "DIMRND" 0)
(setvar "DIMSAH" 0)
(setvar "DIMSD1" 0)
(setvar "DIMSD2" 0)
(setvar "DIMSE1" 0)
(setvar "DIMSE2" 0)
(setvar "DIMSHO" 1)
(setvar "DIMSOXD" 0)
(setvar "DIMTAD" 1)
(setvar "DIMTDEC" 2)
(setvar "DIMTFAC" 1)
(setvar "DIMTIH" 0)
(setvar "DIMTIX" 0)
(setvar "DIMTM" 0)
(setvar "DIMTMOVE" 0)
(setvar "DIMTOFL" 1)
(setvar "DIMTOH" 0)
(setvar "DIMTOL" 0)
(setvar "DIMTOLJ" 0)
(setvar "DIMTP" 0)
(setvar "DIMTSZ" 0)
(setvar "DIMTVP" 0)
(setvar "DIMTXT" 2.5)
(setvar "DIMTZIN" 8)
(setvar "DIMUNIT" 2)
(setvar "DIMUPT" 0)
(setvar "DIMZIN" 8)
(setvar "DISPSILH" 0)
(setvar "DONUTID" 0.5)
(setvar "DONUTOD" 1)
(setvar "DRAGMODE" 2)
(setvar "DRAGP1" 0)
(setvar "DRAGP2" 0)
(setvar "DRAWORDERCTL" 3)
(setvar "DWGCHECK" 0)
(setvar "DYNDIGRIP" 6)
(setvar "DYNDIVIS" 2)
(setvar "DYNMODE" 3)
(setvar "DYNPICOORDS" 0)
(setvar "DYNPIFORMAT" 0)
(setvar "DYNPIVIS" 1)
(setvar "DYNPROMPT" 1)
(setvar "DYNTOOLTIPS" 1)
(setvar "EDGEMODE" 0)
(setvar "ELEVATION" 0)
(setvar "EXPERT" 0)
(setvar "EXPLMODE" 1)
(setvar "EXTNAMES" 1)
(setvar "FACETRATIO" 0)
(setvar "FACETRES" 0.5)
(setvar "FIELDDISPLAY" 1)
(setvar "FIELDEVAL" 31)
(setvar "FILEDIA" 1)
(setvar "FILLETRAD" 0)
(setvar "FILLMODE" 1)
(setvar "GFANG" 0)
(setvar "GFCLR1" "RGB:000,000,255")
(setvar "GFCLR2" "RGB:255,255,153")
(setvar "GFCLRLUM" 1)
(setvar "GFCLRSTATE" 1)
(setvar "GFNAME" 1)
(setvar "GFSHIFT" 0)
(setvar "GRIDMODE" 0)
(setvar "GRIDUNIT" '(10.0 10.0) )
(setvar "GRIPBLOCK" 0)
(setvar "GRIPCOLOR" 160)
(setvar "GRIPHOT" 1)
(setvar "GRIPHOVER" 3)
(setvar "GRIPOBJLIMIT" 100)
(setvar "GRIPS" 1)
(setvar "GRIPSIZE" 5)
(setvar "GRIPTIPS" 1)
(setvar "HALOGAP" 0)
(setvar "HIDEPRECISION" 0)
(setvar "HIDETEXT" 1)
(setvar "HIGHLIGHT" 1)
(setvar "HPANG" 0)
(setvar "HPASSOC" 1)
(setvar "HPBOUND" 1)
(setvar "HPDOUBLE" 0)
(setvar "HPDRAWORDER" 3)
(setvar "HPGAPTOL" 10)
(setvar "HPINHERIT" 0)
(setvar "HPOBJWARNING" 10000)
(setvar "HPORIGIN" '(0.0 0.0) )
(setvar "HPORIGINMODE" 0)
(setvar "HPSCALE" 1)
(setvar "HPSEPARATE" 0)
(setvar "HPSPACE" 1)
(setvar "HYPERLINKBASE" "")
(setvar "IMAGEHLT" 0)
(setvar "INDEXCTL" 0)
(setvar "INETLOCATION" "http://www.autodesk.com")
(setvar "INPUTHISTORYMODE" 15)
(setvar "INSBASE" '(0.0 0.0 0.0) )
(setvar "INSUNITS" 4)
(setvar "INSUNITSDEFSOURCE" 4)
(setvar "INSUNITSDEFTARGET" 4)
(setvar "INTERSECTIONCOLOR" 257)
(setvar "INTERSECTIONDISPLAY" 0)
(setvar "ISAVEBAK" 1)
(setvar "ISAVEPERCENT" 50)
(setvar "ISOLINES" 4)
(setvar "LASTPOINT" '(0.0 0.0 0.0) )
(setvar "LAYOUTREGENCTL" 0)
(setvar "LAZYLOAD" 0)
(setvar "LIMCHECK" 0)
(setvar "LIMMAX" '(420.0 297.0) )
(setvar "LIMMIN" '(0.0 0.0) )
(setvar "LISPINIT" 1)
(setvar "LOCKUI" 1)
(setvar "LUNITS" 2)
(setvar "LUPREC" 4)
(setvar "LWDEFAULT" 25)
(setvar "LWDISPLAY" 0)
(setvar "LWUNITS" 1)
(setvar "MAXACTVP" 64)
(setvar "MAXSORT" 1000)
(setvar "MBUTTONPAN" 1)
(setvar "MEASUREINIT" 1)
(setvar "MEASUREMENT" 1)
(setvar "MENUCTL" 1)
(setvar "MENUECHO" 0)
(setvar "MIRRTEXT" 0)
(setvar "MSOLESCALE" 1)
(setvar "MTEXTFIXED" 2)
(setvar "MTJIGSTRING" "abc")
(setvar "NOMUTT" 0)
(setvar "OBSCUREDCOLOR" 257)
(setvar "OBSCUREDLTYPE" 0)
(setvar "OFFSETDIST" -1)
(setvar "OFFSETGAPTYPE" 0)
(setvar "OLEFRAME" 2)
(setvar "OLEHIDE" 0)
(setvar "OLEQUALITY" 3)
(setvar "OLESTARTUP" 0)
(setvar "ORTHOMODE" 0)
(setvar "OSMODE" 6399)
(setvar "OSNAPCOORD" 1)
(setvar "OSNAPHATCH" 0)
(setvar "OSNAPNODELEGACY" 0)
(setvar "OSNAPZ" 0)
(setvar "PAPERUPDATE" 0)
(setvar "PDMODE" 0)
(setvar "PDSIZE" 0)
(setvar "PEDITACCEPT" 1)
(setvar "PELLIPSE" 0)
(setvar "PICKADD" 1)
(setvar "PICKAUTO" 1)
(setvar "PICKBOX" 3)
(setvar "PICKDRAG" 0)
(setvar "PICKFIRST" 1)
(setvar "PICKSTYLE" 1)
(setvar "PLINEGEN" 0)
(setvar "PLINETYPE" 2)
(setvar "PLINEWID" 0)
(setvar "PLOTOFFSET" 0)
(setvar "PLOTROTMODE" 2)
(setvar "PLQUIET" 0)
(setvar "POLARADDANG" "45;135;225;315")
(setvar "POLARANG" (DegreesToRadians 10))
(setvar "POLARDIST" 0)
(setvar "POLARMODE" 6)
(setvar "POLYSIDES" 4)
(setvar "PREVIEWEFFECT" 2)
(setvar "PREVIEWFILTER" 7)
(setvar "PROJMODE" 1)
(setvar "PROXYGRAPHICS" 1)
(setvar "PROXYNOTICE" 0)
(setvar "PROXYSHOW" 1)
(setvar "PROXYWEBSEARCH" 0)
(setvar "PSLTSCALE" 1)
(setvar "PSPROLOG" "")
(setvar "PSQUALITY" 75)
(setvar "PSTYLEPOLICY" 1)
(setvar "PSVPSCALE" 0)
(setvar "QTEXTMODE" 0)
(setvar "QUEUEDREGENMAX" 2147483647)
(setvar "RASTERDPI" 300)
(setvar "RASTERPREVIEW" 1)
(setvar "RECOVERYMODE" 2)
(setvar "REGENMODE" 1)
(setvar "REMEMBERFOLDERS" 1)
(setvar "REPORTERROR" 1)
(setvar "RTDISPLAY" 1)
(setvar "SAVETIME" 15)
(setvar "SDI" 0)
(setvar "SELECTIONAREA" 1)
(setvar "SELECTIONAREAOPACITY" 25)
(setvar "SELECTIONPREVIEW" 3)
(setvar "SHADEDGE" 3)
(setvar "SHADEDIF" 70)
(setvar "SHORTCUTMENU" 27)
(setvar "SIGWARN" 1)
(setvar "SKETCHINC" 1)
(setvar "SKPOLY" 0)
(setvar "SNAPANG" 0)
(setvar "SNAPBASE" '(0.0 0.0) )
(setvar "SNAPISOPAIR" 0)
(setvar "SNAPMODE" 0)
(setvar "SNAPSTYL" 0)
(setvar "SNAPTYPE" 1)
(setvar "SNAPUNIT" '(10.0 10.0) )
(setvar "SOLIDCHECK" 1)
(setvar "SORTENTS" 127)
(setvar "SPACESWITCH" 1)
(setvar "SPLFRAME" 0)
(setvar "SPLINESEGS" 8)
(setvar "SPLINETYPE" 6)
(setvar "SSLOCATE" 1)
(setvar "SSMAUTOOPEN" 1)
(setvar "STANDARDSVIOLATION" 2)
(setvar "STARTUP" 0)
(setvar "SURFTAB1" 6)
(setvar "SURFTAB2" 6)
(setvar "SURFTYPE" 6)
(setvar "SURFU" 6)
(setvar "SURFV" 6)
(setvar "TABMODE" 0)
(setvar "TBCUSTOMIZE" 1)
(setvar "TEMPOVERRIDES" 1)
(setvar "TEXTEVAL" 0)
(setvar "TEXTFILL" 1)
(setvar "TEXTQLTY" 50)
(setvar "TEXTSIZE" 2.5)
(setvar "THICKNESS" 0)
(setvar "TILEMODE" 1)
(setvar "TOOLTIPS" 1)
(setvar "TRACEWID" 1)
(setvar "TRACKPATH" 0)
(setvar "TRAYICONS" 0)
(setvar "TRAYNOTIFY" 1)
(setvar "TRAYTIMEOUT" 0)
(setvar "TREEDEPTH" 3020)
(setvar "TREEMAX" 10000000)
(setvar "TRIMMODE" 1)
(setvar "TSPACEFAC" 1)
(setvar "TSPACETYPE" 1)
(setvar "TSTACKALIGN" 1)
(setvar "TSTACKSIZE" 70)
(setvar "UCSFOLLOW" 0)
(setvar "UCSICON" 1)
(setvar "UCSORTHO" 1)
(setvar "UCSVIEW" 1)
(setvar "UCSVP" 1)
(setvar "UNITMODE" 0)
(setvar "UPDATETHUMBNAIL" 15)
(setvar "VISRETAIN" 1)
(setvar "VTDURATION" 750)
(setvar "VTENABLE" 3)
(setvar "VTFPS" 7)
(setvar "WHIPARC" 0)
(setvar "WHIPTHREAD" 1)
(setvar "WMFBKGND" 0)
(setvar "WMFFOREGND" 0)
(setvar "WORLDVIEW" 1)
(setvar "XCLIPFRAME" 0)
(setvar "XEDIT" 1)
(setvar "XFADECTL" 50)
(setvar "XLOADCTL" 2)
(setvar "XREFCTL" 0)
(setvar "XREFNOTIFY" 2)
(setvar "XREFTYPE" 1)
(setvar "ZOOMFACTOR" 100)
(menucmd "p30=+Lab2012.POPL1")
(menucmd "p30=+Lab2012.POPL2")
(menucmd "p30=+Lab2012.POPL3")
(command "._layiso" "_S" "_OFF" "_OFF" "" )
)
