(defun pt ()
  (princ " - ")
)

(TERPRI)
(PROMPT "Loading Utility's")
(TERPRI)
(SETVAR "CMDECHO" 0)
(SETVAR "MENUECHO" 0)

(princ "CHT")

(defun c:CHT ()
  (Setvar "cmdecho" 0)
  (setq p (ssget))
  (setq nl (entsel "Indicate object on layer to change to ?"))
  (setq firp (ssname p 0))
  (setq fldet (entget (car nl)))
  (setq lyr (cdr (assoc '8 fldet)))
  (TERPRI)
  (princ "New current layer = ")
  (princ lyr)
  (TERPRI)
  (command "change" p "" "l" lyr)
)

(pt)
(princ "VERBIND")

(defun c:VERBIND ()
  (SETVAR "CMDECHO" 0)
  (setq fline (entsel "Please mark first line "))
  (setq sline (entsel "Please mark second line"))
  (setq orla (getvar "clayer"))
  (setq fldet (entget (car fline)))
  (setq lyr (cdr (assoc '8 fldet)))
  (setq ltype (cdr (assoc '6 fldet)))
  (setq pt1 (nth 1 fline))
  (setq spt (osnap pt1 "endp"))
  (setq pt2 (nth 1 sline))
  (setq ept (osnap pt2 "endp"))
  (command "layer" "s" lyr "")
  (command "linetype" "s" ltype "")
  (command "line" spt ept "")
  (command "layer" "s" orla "")
)

(pt)
(princ "GET")

(DEFUN C:GET ()
  (SETQ R1 (GETVAR "USERR1"))
  (SETQ R2 (GETVAR "USERR2"))
  (SETQ R3 (GETVAR "USERR3"))
  (SETQ R4 (GETVAR "USERR4"))
  (SETQ R5 (GETVAR "USERR5"))
  (SETQ I1 (GETVAR "USERI1"))
  (SETQ I2 (GETVAR "USERI2"))
  (SETQ I3 (GETVAR "USERI3"))
  (SETQ I4 (GETVAR "USERI4"))
  (SETQ I5 (GETVAR "USERI5"))
  (PRINC "\nUSERR1 : ")
  (PRINC R1)
  (PRINC "  PidCAD INDEX ")
  (PRINC "\nUSERR2 : ")
  (PRINC R2)
  (PRINC "\nUSERR3 : ")
  (PRINC R3)
  (PRINC "\nUSERR4 : ")
  (PRINC R4)
  (PRINC "\nUSERR5 : ")
  (PRINC R5)
  (TERPRI)
  (PRINC "\nUSERI1 : ")
  (PRINC I1)
  (PRINC "\nUSERI2 : ")
  (PRINC I2)
  (PRINC "    PidCAD SNAP ")
  (PRINC "\nUSERI3 : ")
  (PRINC I3)
  (PRINC "\nUSERI4 : ")
  (PRINC I4)
  (PRINC "\nUSERI5 : ")
  (PRINC I5)
  (TERPRI)
)

(pt)
(princ "LS")

(defun c:ls ()
  (setq lin (entsel "Indicate line "))
  (setq ldet (entget (car lin)))
  (setq lyr (cdr (assoc '8 ldet)))
  (TERPRI)
  (PRINC "New current layer = ")
  (princ lyr)
  (TERPRI)
  (command "layer" "s" lyr "")
)

(pt)
(princ "DRLINE")

(DEFUN C:DRLINE	()
  (GRAPHSCR)
  (SETQ IPT (GETPOINT "MIDPOINT OF FIRST LINE "))
  (TERPRI)
  (SETQ RA (GETANGLE IPT "ROTATION ANGLE OF CENTERLINE "))
  (TERPRI)
  (SETQ PRA (+ RA (/ PI 2)))
  (SETQ MRA (- RA (/ PI 2)))
  (SETQ LL1 (GETREAL "LENGTH OF LINE "))
  (TERPRI)
  (SETQ LL11 (POLAR IPT PRA (/ LL1 2)))
  (SETQ LL12 (POLAR IPT MRA (/ LL1 2)))
  (COMMAND "LINE" LL11 LL12 "")
  (SETQ LL2 (GETSTRING "DO YOU WANT AN OFFSET OF THIS LINE <Y> "))
  (TERPRI)
  (WHILE (= LL2 "")
    (SETQ LL2 (GETREAL "LENGTH OF LINE "))
    (TERPRI)
    (SETQ DIS (GETREAL "DISTANCE FOR OFFSET "))
    (TERPRI)
    (SETQ IPT (POLAR IPT RA DIS))
    (SETQ LL21 (POLAR IPT PRA (/ LL2 2)))
    (SETQ LL22 (POLAR IPT MRA (/ LL2 2)))
    (COMMAND "LINE" LL21 LL22 "")
    (SETQ CONN (GETSTRING "DO YOU WANT TO CONNECT THE LINES <Y>"))
    (TERPRI)
    (WHILE (= CONN "")
      (initget "Perpendicular Endpoints")
      (setq xx (getkword "\nPerpendicular/<Endpoints>: "))
      (cond ((= xx "Perpendicular") (perp))
	    ((= xx "Endpoints") (endp))
	    ((= xx nil) (endp))
      )
      (setq conn "n")
      (setq ll11 ll21)
      (setq ll12 ll22)
    )
    (SETQ LL2 (GETSTRING "DO YOU WANT AN OFFSET OF THIS LINE <Y> "))
    (TERPRI)
  )
)
(defun perp ()
  (SETQ DIS1 (DISTANCE LL11 LL12))
  (SETQ DIS2 (DISTANCE LL21 LL22))
  (IF (< DIS1 DIS2)
    (PROGN
      (SETQ L1 LL11)
      (SETQ L2 LL12)
      (SETQ NRA RA)
    )
    (PROGN
      (SETQ L1 LL21)
      (SETQ L2 LL22)
      (SETQ NRA (+ RA PI))
    )
  )
  (setq point1 (polar l1 Nra dis))
  (setq point2 (polar l2 Nra dis))
  (command "line" l1 point1 "")
  (command "line" l2 point2 "")
)

(defun endp ()
  (command "line" ll11 ll21 "")
  (command "line" ll12 ll22 "")
)

(PT)
(princ "NEWLINE")

(DEFUN C:NEWLINE ()
  (SETQ P (SSGET))
  (SETQ NL (GETREAL "NEW LINE-LENGTH "))
  (IF P
    (PROGN
      (SETQ L (SSLENGTH P))
      (SETQ LUS 0)
      (WHILE (/= LUS L)
	(SETQ INF (ENTGET (SETQ E (SSNAME P LUS))))
	(SETQ LAY (CDR (ASSOC 8 INF)))
	(SETQ PT1 (CDR (ASSOC 10 INF)))
	(SETQ PT2 (CDR (ASSOC 11 INF)))
	(MIDDLE)
	(NWPOINTS)
	(COMMAND ".ERASE" E "")
	(COMMAND ".LAYER" "S" LAY "")
	(COMMAND ".LINE" PT1 PT2 "")
	(SETQ LUS (1+ LUS))
      )
    )
    (WRITE-LINE "YOU HAVE TO SELECT SOMETHING")
  )
)


(DEFUN NWPOINTS	()
  (SETQ PRA (ANGLE IPOINT PT1))
  (SETQ MRA (ANGLE IPOINT PT2))
  (SETQ HL (/ NL 2))
  (SETQ PT1 (POLAR IPOINT PRA HL))
  (SETQ PT2 (POLAR IPOINT MRA HL))
)

    ;********************************************
    ;**********     DEELPROGAMMA'S     **********
    ;********************************************


(DEFUN *ERROR* (ST)
  (MODER)
  (TERPRI)
  (PRINC "\nERROR: ")
  (PRINC ST)
  (PRINC)
)

(DEFUN MIDDLE ()
  (SETQ X (/ (+ (CAR PT1) (CAR PT2)) 2))
  (SETQ Y (/ (+ (CADR PT1) (CADR PT2)) 2))
  (SETQ X1 (* X X))
  (SETQ Y1 (+ Y Y))
  (SETQ PTL (LIST X1 Y1))
  (SETQ IPOINT (LIST X Y))
)

(DEFUN MODER ()
  (REPEAT (LENGTH MLST)
    (SETVAR (CAAR MLST) (CADAR MLST))
    (SETQ MLST (CDR MLST))
  )
)
