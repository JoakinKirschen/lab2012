(DEFUN C:CROSS (/ err line1 line2)
  
  (SETQ err "")
  (setq GAP 2.0)
  (SETQ line2 (ENTSEL "Select crossing line: "))
  (PRINC "\n")
  (IF (= line2 nil)
    (PROGN
      (SETQ err "\nNo Line selected.")
    )
    (PROGN
      (SETQ line1 (ENTSEL "Select line to cut: "))
      (PRINC "\n")
      (IF (= line1 nil)
	(PROGN
	  (SETQ err "\nNo Line selected.")
	)
      )
    )
  )
  (IF (= err "")
    (PROGN
      (SETQ l1 (CAR line1))
      (SETQ l2 (CAR line2))
      (SETQ l1info (ENTGET l1))
      (SETQ l2info (ENTGET l2))
      (IF (OR (/= (CDR (ASSOC 0 l1info)) "LINE")
	      (/= (CDR (ASSOC 0 l2info)) "LINE")
	  )
	(PROGN
	  (SETQ err "\nNo Lines selected.")
	)
      )
    )
  )
  (IF (= err "")
    (PROGN
      (SETQ pt1 (CDR (ASSOC 10 l1info)))
      (SETQ pt2 (CDR (ASSOC 11 l1info)))
      (IF (> (CAR pt1) (CAR pt2))
	(PROGN
	  (SETQ pt3 pt1)
	  (SETQ pt1 pt2)
	  (SETQ pt2 pt3)
	)
      )
      (SETQ pt3 (CDR (ASSOC '10 l2info)))
      (SETQ pt4 (CDR (ASSOC '11 l2info)))
      (SETQ IPOINT (INTERS pt1 pt2 pt3 pt4 nil))
      (IF (= IPOINT nil)
	(PROGN
	  (SETQ err "\n No intersection of 2 lines.")
	)
      )
    )
  )
  (princ "\n")
  (IF (= err "")
    (PROGN
      (SETQ ix (CAR IPOINT))
      (SETQ iy (CADR IPOINT))
      (SETQ hoek (ANGLE pt1 pt2))
      (SETQ x5 (- ix (* GAP (COS hoek))))
      (SETQ y5 (- iy (* GAP (SIN hoek))))
      (SETQ x6 (+ ix (* GAP (COS hoek))))
      (SETQ y6 (+ iy (* GAP (SIN hoek))))
      (SETQ pt5 (LIST x5 y5))
      (SETQ pt6 (LIST x6 y6))
      (COMMAND "BREAK" line1 "F" pt5 pt6)
      (COMMAND "LAYER" "S" "0" "")
    )
    (WRITE-LINE err)
  )
  (PRINT)
)
