;;-----[ Deze functie altijd laten staan]------------------------------------
(defun L12_SETTINGS ()
(princ "L12_SETTINGS is loaded")
(princ)
)

(defun c:L12_Settings ( / temp Radio1$ list1 list2 disc Dcl_Id% autosave)
	(initerr)  (setvar "cmdecho" 0)
	(setq list2 (list "AC-" "TI-" "ME-" "EI-"))
	(setq Dcl_Id% (load_dialog "LAB2012.dcl"))
	(if (not (new_dialog "L12_Settings" Dcl_Id%))
	(exit))
	
	(if (setq Radio1$ (getenv "L12_UpdateSettings"))nil(setenv "L12_UpdateSettings" (vl-princ-to-string 2)))
	(if (setq autosave (getenv "L12_AutosaveSettings"))nil(setenv "L12_AutosaveSettings" (vl-princ-to-string 50)))
	
	;(if (getenv "L12_UpdatePath")
	;(if (findfile (getenv "L12_UpdatePath"))
	;(set_tile "u_path_text" (vl-filename-directory (getenv "L12_UpdatePath")))
	;(set_tile "u_path_text" "Update path not set!")
	;)
	;(set_tile "u_path_text" "Update path not set!")
	;)
	
	;(if (getenv "L12_ExcelPath")
	;(if (findfile (getenv "L12_ExcelPath"))
	;(set_tile "e_path_text" (vl-filename-directory (getenv "L12_ExcelPath")))
	;(set_tile "e_path_text" "Excel path not set!")
	;)
	;(set_tile "e_path_text" "Excel path not set!")
	;)
	
	(set_tile "Radio1" Radio1$)
	(set_tile "Check1" autosave)
	
	(if (getenv "L12_Disipline")
	(set_tile_list "Discipline" list2 (setq disc(getenv "L12_Disipline")))
	(set_tile_list "Discipline" list2 "AC-")	
	)
	
	
	
	(action_tile "Discipline" "(setq disc (nth (atoi $value) list2))")
	(action_tile "Radio1" "(setq Radio1$ $value)")
	(action_tile "Check1"  "(check_editint \"autosave\")(print autosave)" )
	;(action_tile "Check1" "(setq Check1$ $value)")
	(action_tile "back" "(setq temp 0)(done_dialog)")
	(action_tile "ok" "(setq temp 1)(done_dialog)")
	;(action_tile "u_path_but" "(L12_LabSetUpdatepath)")
	;(action_tile "e_path_but" "(L12_LabSetExcelpath)")
	
	(start_dialog)
	(unload_dialog Dcl_Id%)
	(setq list1 (list temp toggle1$))
	(if (= temp 1)
	(progn
	(setq gl_autosave (atoi autosave))
	(setenv "L12_UpdateSettings" Radio1$)
	(setenv "L12_AutosaveSettings" autosave)
	(setenv "L12_Disipline" disc)
	)
	)
	(reset)
	(princ)
)

;(defun L12_LabSetUpdatepath ( / temp)
;    (setq temp (getfiled "search lab_version.txt" "lab_version.txt" "txt" 0))
;	(if (/= temp nil)
;	(progn
;	(while (and (/= temp nil)(/= (vl-filename-base temp) "lab_version"))
;	(setq temp (getfiled "search lab_version.txt" "lab_version.txt" "txt" 0))
;	)
;	))
;	(if (/= temp nil)
;	(if (findfile temp)
;	(progn
;	(setenv "L12_UpdatePath" temp)
;	(set_tile "u_path_text" (vl-filename-directory temp))
;	)))
;(princ)	
;)

;(defun L12_LabSetExcelpath ( / temp)
;    (setq temp (getfiled "search excel.exe" "EXCEL.EXE" "exe" 0))
;	(if (/= temp nil)
;	(progn
;	(while (and (/= temp nil)(/= (vl-filename-base temp) "EXCEL"))
;	(setq temp (getfiled "search excel.exe" "EXCEL.EXE" "exe" 0))
;	)
;	))
;	(if (/= temp nil)
;	(if (findfile temp)
;	(progn
;	(setenv "L12_ExcelPath" temp)
;	(set_tile "e_path_text" (vl-filename-directory temp))
;	)))
;(princ)	
;)
