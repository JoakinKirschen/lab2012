(defun c:CHTL ()
 (setq cmd (getvar "cmdecho" ))  (setvar "cmdecho" 0)
  (setq p (ssget))
  (setq nl (entsel "Indicate object on linetype to change to ?"))
  (setq firp (ssname p 0))
  (setq fldet (entget (car nl)))
  (setq lyr (cdr (assoc '6 fldet)))
  (TERPRI)
  (princ "New current ltype = ")
  (princ lyr)
  (terpri)
  (command "change" p "" "P" "LT" lyr "")
  (princ)
)
