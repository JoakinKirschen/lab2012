; ?-??? PurgeAllGroups
; ??????? ???????? ???? ?????
; ???????? [???]:
;   ???
; ??????????: Nil
(vl-load-com)
  (defun PurgeAllGroups (/ grpList index grp)
  (setq grpList (dictsearch (namedobjdict) "ACAD_GROUP"))
  (setq index 1)
  (while (setq grp (nth index grplist))
    (if  (= (car grp) 3)
      (entdel (cdr (nth (+ index 1) grplist)))
    )
    (setq index (+ 1 index))
  )
  (princ))

; ?-??? PurgeEmptyGroups
; ??????? ???????? ???? ?????? ?????
; ???????? [???]:
;   Named = ??? [INT]
;       0 — ?????? ??????????? ??????
;       1 — ?????? ????????????? ??????
;   t,nil — ??? ??????
; ??????????: Nil
(defun PurgeEmptyGroups ( named / grpList index grp egrp named_list e_list)
  ;;; ???????????? ?-???, ?????????? multiple group code
(defun massoc (key alist / x nlist)
  (foreach x alist
    (if (eq key (car x))
      (setq nlist (cons (cdr x) nlist))
    ))
  (reverse nlist))
  (setq named_list '(0 1))
  (if (member named named_list)(setq named_list (list named)))
  (setq grpList (dictsearch (namedobjdict) "ACAD_GROUP"))
  (setq index 1)
  (while (setq grp (nth index grplist))
    (if  (= (car grp) 3)
      (progn
  (setq egrp (entget (cdr (nth (+ index 1) grplist))))
  (if (member (cdr (assoc 70 egrp)) named_list)
    (progn
      (setq e_list (massoc 340 egrp))
      (if(not (vl-member-if 'entget e_list))
        (entdel (cdr (nth (+ index 1) grplist)))
        )
      )
    )
  )
      )
    (setq index (+ 1 index))
  )
  (princ))


; ?-??? PurgeAllUnNamedGroups
; ??????? ???????? ???? ????????? ????? *Annn
; ???????? [???]:
; ???
; ??????????: Nil
(defun PurgeAllUnNamedGroups (/ grpList index grp)
  (setq grpList (dictsearch (namedobjdict) "ACAD_GROUP"))
  (setq index 1)
  (while (setq grp (nth index grplist))
    (if  (= (car grp) 3)
      (progn
  (if (= (chr 42) (substr (cdr grp) 1 1))
    (entdel (cdr (nth (+ index 1) grplist)))
  )
      )
    )
    (setq index (+ 1 index))
  )
  (princ)
)

; ?-??? DeleteGroupbyName
; ???????? ?????? ?? ?????.
; ???????? [???]:
;   Name = ??? ?????? [STR]
; ??????????: Null
(defun DeleteGroupbyName (Name)
(or *kpblc-activedoc*
   (setq *kpblc-activedoc* (vla-get-activedocument (vlax-get-acad-object)))
)
 (vl-catch-all-apply
 '(lambda ()
   (vla-delete
    (vla-item
     (vla-get-groups *kpblc-activedoc*)
     Name
    )
   )
  )
 )
 (princ)
)

; ?-??? GetObjGroupNames
; ?????????? ?????? ???? ????? ??????? ??? nil.
; Arguments [Type]:
;   Obj = Object [VLA-OBJECT]
;   Obj = Object [ENAME]
; ?????????? [Type]:
;   ?????? ???? ?????[LIST]
;
(defun GetObjGroupNames (Obj / Cur_ID NmeLst)
 (or *kpblc-activedoc*
   (setq *kpblc-activedoc* (vla-get-activedocument (vlax-get-acad-object)))
)
 (if (= (type Obj) 'ENAME)(setq Obj (vlax-ename->vla-object Obj)))
 (setq Cur_ID (vla-get-ObjectID Obj))
 (vlax-for Grp (vla-get-Groups *kpblc-activedoc*)
  (vlax-for Ent Grp
   (if (equal (vla-get-ObjectID Ent) Cur_ID)
    (setq NmeLst (cons (vla-get-Name Grp) NmeLst))
   )
   (vlax-release-object Ent)
  )
  (vlax-release-object Grp)
 )
 (reverse NmeLst)
)

 ;;;??????? ??? ?????? ?????? (??????????? ? ?????????????)
 ;;;????????, ???????? ? ?????? ????????, ? ???????? ????? ????????
 ;;;http://dwg.ru/forum/viewtopic.php?t=4762
(defun PurgeAllEmptyGroups  ()(PurgeEmptyGroups t))
 ;;;??????? ??? ?????? ?????? (???????????)
(defun PurgeAllNamedEmptyGroups  ()(PurgeEmptyGroups 0))
 ;;;??????? ??? ?????? ?????? (?????????????)
(defun PurgeAllUnNamedEmptyGroups  ()(PurgeEmptyGroups 1))
;;;=======================================================
;;; ???????
;;;=======================================================
;;; ??????? ??? ?????? Purge All Groups
(defun C:PAG ()(PurgeAllGroups))
;;; ??????? ??? ?????? ??????   Purge Empty Groups
(defun C:PEG ()(PurgeAllEmptyGroups))
;;; ??????? ??? ????????????? ??????  Purge Unnamed Groups
(defun C:PUG ()(PurgeAllUnNamedGroups))
