(prompt "\nCreatie van een aantal basis LAB2012 layers\n")
(defun C:L12_GMI2DLAYER ( / )
;	ALGEMEEN
    (setvar "cmdecho" 0)
   (princ "\nLayers ALGEMEEN...")
      (mfixLayer "0000-AFBRAAK-co-12" "3" "continuous" "default" 1)
      (mfixLayer "0000-HULPLIJN-co-bruin"    "36"     "continuous" "default"   0     )
      (mfixLayer "0000-VIEW-co-06"    "1"     "continuous" "default"   0     )
      (mfixLayer "0000-ALGEMEEN-co-25"   "7"     "continuous" "default"  1  )
      (mfixLayer "0000-ILLUSTRATIE-co-06"   "1"     "continuous" "default"  1  )
      (mfixLayer "0100-SYMBOOL-co-25"   "7"     "continuous" "default" 1   )
      (mfixLayer "0200-MAAT"   "7"     "continuous" "default" 1   )
      (mfixLayer "0300-TEKST-25"   "7"     "continuous" "default" 1   )
      (mfixLayer "0300-TEKST-35"   "2"     "continuous" "default" 1   )
      (mfixLayer "0300-TEKST-50"   "6"     "continuous" "default" 1   )
      (mfixLayer "0300-TEKST-70"   "4"     "continuous" "default" 1   )
      (mfixLayer "0400-SCOPE-co-50"   "6"     "continuous" "default" 1   )
      (mfixLayer "0500-ARCERING-06"   "1"     "continuous" "default" 1   )
      (mfixLayer "0500-ARCERING-12"   "3"     "continuous" "default" 1   )
      (mfixLayer "0500-ARCERING-grijs"   "9"     "continuous" "default" 1   )
      (mfixLayer "0500-ARCERING-OMTREK-co-06"    "1"     "continuous" "default"   0     )
      (mfixLayer "0600-ASLIJN-dd-06"   "1"     "dashdot" "default" 1   )
      (mfixLayer "0600-ASLIJN-dd-12"   "3"     "dashdot" "default" 1   )
;	CIVIEL
   (princ "\nLayers CIVIEL...")
      (mfixLayer "1000-PALEN-co-35"   "2"     "continuous" "default" 1   )
      (mfixLayer "1100-FUNDERINGEN-co-35"   "2"     "continuous" "default" 1   )
      (mfixLayer "1100-FUNDERINGEN-co-50"   "6"     "continuous" "default" 1   )
      (mfixLayer "1100-FUNDERINGEN-hi2-35"   "2"     "hidden2" "default" 1   )
      (mfixLayer "1100-FUNDERINGEN-hi2-50"   "6"     "hidden2" "default" 1   )
      (mfixLayer "1200-AARDING-dd2-70"   "4"     "dashdot2" "default" 1   )
      (mfixLayer "1300-BETONSTRUCTUUR-co-25"   "7"     "continuous" "default" 1   )
      (mfixLayer "1300-BETONSTRUCTUUR-co-35"   "2"     "continuous" "default" 1   )
      (mfixLayer "1300-BETONSTRUCTUUR-co-50"   "6"     "continuous" "default" 1   )
      (mfixLayer "1300-BETONSTRUCTUUR-hi2-25"   "7"     "hidden2" "default" 1   )
      (mfixLayer "1300-BETONSTRUCTUUR-hi2-35"   "2"     "hidden2" "default" 1   )
      (mfixLayer "1300-BETONSTRUCTUUR-hi2-50"   "6"     "hidden2" "default" 1   )
      (mfixLayer "1400-METSELWERK-co-25"   "7"     "continuous" "default" 1   )
      (mfixLayer "1400-METSELWERK-co-35"   "2"     "continuous" "default" 1   )
      (mfixLayer "1400-METSELWERK-hi2-25"   "7"     "hidden2" "default" 1   )
      (mfixLayer "1400-METSELWERK-hi2-35"   "2"     "hidden2" "default" 1   )
      (mfixLayer "1500-WAPENING-co-50"   "6"     "continuous" "default" 1   )
      (mfixLayer "1500-WAPENING-co-70"   "4"     "continuous" "default" 1   )
      (mfixLayer "1510-ONDERWAPENING-co-70"   "4"     "continuous" "default" 1   )
      (mfixLayer "1520-BOVENWAPENING-hi-70"   "4"     "hidden" "default" 1   )
      (mfixLayer "1530-SNEDEWAPENING-co-70"   "4"     "continuous" "default" 1  )
;	STAAL
   (princ "\nLayers STAAL...")
      (mfixLayer "2000-STAAL-ALGEMEEN-co-06"   "1"     "continuous" "default" 1   )
      (mfixLayer "2000-STAAL-ALGEMEEN-hi2-06"   "1"     "hidden2" "default" 1   )
      (mfixLayer "2000-STAAL-ALGEMEEN-dd2-06"   "1"     "dashdot2" "default" 1   )
      (mfixLayer "2000-STAAL-ALGEMEEN-co-25"   "7"     "continuous" "default" 1   )
      (mfixLayer "2000-STAAL-ALGEMEEN-co-35"   "2"     "continuous" "default" 1   )
      (mfixLayer "2000-STAAL-ALGEMEEN-co-50"   "6"     "continuous" "default" 1   )
      (mfixLayer "2100-STAAL-PROF-co-35"   "2"     "continuous" "default" 1   )
      (mfixLayer "2100-STAAL-PRSTIP-hi2-12"   "3"     "hidden2" "default" 1   )
      (mfixLayer "2200-STAAL-LEUNING-dd2-70"   "4"     "dashdot2" "default" 1   )
      (mfixLayer "2300-STAAL-PLAAT-co-35"   "2"     "continuous" "default" 1   )
      (mfixLayer "2300-STAAL-PLAAT-hi2-12"   "3"     "hidden2" "default" 1   )
;	ARCHITECTUUR
   (princ "\nLayers ARCHITECTUUR...")
;	INFRASTRUCTUUR
   (princ "\nLayers INFRASTRUCTUUR...")
      (mfixLayer "4800-RIOLERING-ce-35" "2"     "center" "default" 1   )
      (mfixLayer "4810-REGENWATER-ce2-06" "1"     "center2" "default" 1   )
      (mfixLayer "4820-AFVALWATER-ph2-06"   "1"     "phantom2" "default" 1   )
      (mfixLayer "4830-CHEMICALIEN-di2-06"   "1"     "divide2" "default" 1   )
      (mfixLayer "4840-FECALIEN-bo2-06"   "1"     "border2" "default" 1   )
      (mfixLayer "4810-REGENWATER-ce2-35"   "2"     "center2" "default" 1   )
      (mfixLayer "4820-AFVALWATER-ph2-35"   "2"     "phantom2" "default" 1   )
      (mfixLayer "4830-CHEMICALIEN-di2-35"   "2"     "divide2" "default" 1   )
      (mfixLayer "4840-FECALIEN-bo2-35"   "2"     "border2" "default" 1   )


   (Princ "\nLayerset is aangemaakt.")
   (setvar "CLAYER" (strcat (getenv "L12_Disipline") "0000-ALGEMEEN-co-25"))
  (princ)
)
