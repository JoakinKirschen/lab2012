;;-----[ Deze functie altijd laten staan]------------------------------------
(defun L12_BLOCKS ()
(princ "L12_BLOCKS is loaded")
(princ)
)

;;-----[ Functie die geschaalde blocks plaatst]--------------------

  (defun C:BInsertSc ( / schaal BlockName ipt )
    (initerr)  
	(L12_checkinstel)
	(setvar "cmdecho" 0)
    (if (not (inPspace))
    (setq schaal (L12_getschaal))
    (setq schaal 1)
    )
    (setq BlockName (getstring "\nSymbool: "))
    (setq ipt (getpoint "Geef insertiepunt: "))
    (if (or (tblsearch "BLOCK" BlockName)
	 (findfile (strcat BlockName ".dwg"))
      )
    (progn
	  (command "_.INSERT" BlockName)
      (command)
      (If (= (L12_BlTest BlockName) 1)
          (command "._Insert" BlockName ipt schaal "")
          (command "._Insert" BlockName ipt schaal schaal "")
      )
    )
    (progn
      (princ (strcat "\nOpgegeven symbool '" BlockName "' niet gevonden!\n"))
    )
    )
    (reset)
    (princ)
  )


;;-----[ Functie die in meerdere talen geschaalde blocks plaatst]--------------------

  (defun C:BInsertScLa ( / schaal taal BlockName ipt sufix )
    (initerr) 
    (L12_checkinstel)	
	(setvar "cmdecho" 0)
    (if (not (inPspace))
    (setq schaal (L12_getschaal))
    (setq schaal 1)
    )
    (setq taal (L12_getlang))
    (Cond 
      ((= taal 1) (setq sufix "N"))
      ((= taal 2) (setq sufix "F"))
      ((= taal 3) (setq sufix "E"))
    )    ;cond modelspace
    (setq BlockName (strcat (getstring "\nSymbool: ") sufix))
    (setq ipt (getpoint "Geef insertiepunt: "))
    (if (or (tblsearch "BLOCK" BlockName)
	 (findfile (strcat BlockName ".dwg"))
      )
    (progn
	  (command "_.INSERT" BlockName)
      (command)
      (If (= (L12_BlTest BlockName) 1)
          (command "._Insert" BlockName ipt schaal "")
          (command "._Insert" BlockName ipt schaal schaal "")
      )
    )
    (progn
      (princ (strcat "\nOpgegeven symbool '" BlockName "' niet gevonden!\n"))
    )
  )
  (reset)
  (princ)
)
(princ)

(defun C:BInsertScLaEx ( / schaal taal BlockName ipt sufix prestring)
    (initerr) 
    (L12_checkinstel)	
	(setvar "cmdecho" 0)
    (if (not (inPspace))
    (setq schaal (L12_getschaal))
    (setq schaal 1)
    )
    (setq taal (L12_getlang))
    (Cond 
      ((= taal 1) (setq sufix "N"))
      ((= taal 2) (setq sufix "F"))
      ((= taal 3) (setq sufix "E"))
    )    ;cond modelspace
	(setq prestring (L12_standard_BInsertScLaEx))
    (setq BlockName (strcat prestring (getstring "\nSymbool: ") sufix))
    (setq ipt (getpoint "Geef insertiepunt: "))
    (if (or (tblsearch "BLOCK" BlockName)
	 (findfile (strcat BlockName ".dwg"))
      )
    (progn
	  (command "_.INSERT" BlockName)
      (command)
;      (If (= (L12_BlTest BlockName) 1)
          (command "._Insert" (strcat "*" BlockName) ipt schaal "")
;          (command "._Insert" (strcat "*" BlockName) ipt schaal schaal "")
;      )
    )
    (progn
      (princ (strcat "\nOpgegeven symbool '" BlockName "' niet gevonden!\n"))
    )
  )
  (reset)
  (princ)
)

(defun L12_BInsertScLa (BlockName / schaal taal BlockName ipt sufix prestring)
    (initerr) 
    (L12_checkinstel)	
	(setvar "cmdecho" 0)
    (if (not (inPspace))
    (setq schaal (L12_getschaal))
    (setq schaal 1)
    )
    (setq taal (L12_getlang))
    (Cond 
      ((= taal 1) (setq sufix "N"))
      ((= taal 2) (setq sufix "F"))
      ((= taal 3) (setq sufix "E"))
    )    ;cond modelspace
	(setq prestring (L12_standard_BInsertScLa))
	(setq BlockName (strcat prestring BlockName sufix))
    (setq ipt (getpoint "Geef insertiepunt: "))
    (if (or (tblsearch "BLOCK" BlockName)
	 (findfile (strcat BlockName ".dwg"))
      )
    (progn
	  (command "_.INSERT" BlockName)
      (command)
      (If (= (L12_BlTest BlockName) 1)
          (command "._Insert" BlockName ipt schaal "")
          (command "._Insert" BlockName ipt schaal schaal "")
      )
    )
    (progn
      (princ (strcat "\nOpgegeven symbool '" BlockName "' niet gevonden!\n"))
    )
  )
  (reset)
  (princ)
)

(defun L12_BInsertSc (BlockName / schaal taal BlockName ipt prestring)
    (initerr) 
    (L12_checkinstel)	
	(setvar "cmdecho" 0)
    (if (not (inPspace))
    (setq schaal (L12_getschaal))
    (setq schaal 1)
    )
	(setq prestring (L12_standard_BInsertScLa))
	(setq BlockName (strcat prestring BlockName))
    (setq ipt (getpoint "Geef insertiepunt: "))
    (if (or (tblsearch "BLOCK" BlockName)
	 (findfile (strcat BlockName ".dwg"))
      )
    (progn
	  (command "_.INSERT" BlockName)
      (command)
      (If (= (L12_BlTest BlockName) 1)
          (command "._Insert" BlockName ipt schaal "")
          (command "._Insert" BlockName ipt schaal schaal "")
      )
    )
    (progn
      (princ (strcat "\nOpgegeven symbool '" BlockName "' niet gevonden!\n"))
    )
  )
  (reset)
  (princ)
)


;;-----[ Functie die blocks geschaald plaatst]----------------

(defun BInsertScaled ( BlockName ipt / schaal )
  (initerr)  
  (L12_checkinstel)
  (setvar "cmdecho" 0)
  (if (not (inPspace))
  (setq schaal (L12_getschaal))
  (setq schaal 1)
  )
 (if (or (tblsearch "BLOCK" BlockName)
	 (findfile (strcat BlockName ".dwg"))
      )
    (progn
	  (command "_.INSERT" BlockName)
      (command)
      (If (= (L12_BlTest BlockName) 1)
          (command "._Insert" BlockName ipt schaal "")
          (command "._Insert" BlockName ipt schaal schaal "")
      )
    )
    (progn
      (princ (strcat "\nOpgegeven symbool '" BlockName "' niet gevonden!\n"))
    )
  )
  (reset)
  (princ)
)

(defun BInsertScaledEx ( BlockName ipt / schaal )
  (initerr)  
  (L12_checkinstel)
  (setvar "cmdecho" 0)
  (if (not (inPspace))
  (setq schaal (L12_getschaal))
  (setq schaal 1)
  )
 (if (or (tblsearch "BLOCK" BlockName)
	 (findfile (strcat BlockName ".dwg"))
      )
    (progn
	  (command "_.INSERT" BlockName)
      (command)
;      (If (= (L12_BlTest BlockName) 1)
          (command "._Insert" (strcat "*" BlockName) ipt schaal "")
;          (command "._Insert" (strcat "*" BlockName) ipt schaal schaal "")
;      )
    )
    (progn
      (princ (strcat "\nOpgegeven symbool '" BlockName "' niet gevonden!\n"))
    )
  )
  (reset)
  (princ)
)

(defun L12_InsBlock (block / ipt c1)
  (setq c1 (getvar "clayer"))
  (setq ipt (getpoint "Geef insertiepunt: "))
  (mfixLayer "0100-SYMBOOL-co-25" "7" "continuous" "default" 1 )
  (BInsertScaled block ipt)
  (setvar "clayer" c1 )
  (princ)
)


;;-----[ Functie die blocks ongeschaald plaatst]--------------

(defun C:BInsertUnsc ( / BlockName ipt)
  (initerr)  
  (L12_checkinstel)
  (setvar "cmdecho" 0)
  (setq BlockName (getstring "\nSymbool? "))
;  (setq fName (findfile (strcat FNAme ".dwg")))
  (setq ipt (getpoint "Geef insertiepunt"))
  (if (or (tblsearch "BLOCK" BlockName)
	 (findfile (strcat BlockName ".dwg"))
      )
    (progn
	  (command "_.INSERT" BlockName)
      (command)
	  (If (= (L12_BlTest BlockName) 1)
      (command "._Insert" BlockName ipt 1 "")
	  (command "._Insert" BlockName ipt 1 1 "")
	  )
    )
    (progn
      (princ "\nOpgegeven symbool is niet gevonden ...")
    )
  )
  (reset)
  (princ)
)


;;-----[ Functies om revisie driehoeken plaatsen]------------

  (defun C:BInsertRevDriehoek1 ( / ipt c1)
	(initerr)  
	(setvar "cmdecho" 0)
	(setq ipt (getpoint "Geef insertiepunt: "))
	(setq c1 (getvar "clayer"))
    (princ "\n")
	(mfixLayer "0100-SYMBOOL-co-25" "7" "continuous" "default" 1 )
    (BInsertScaled "Revisie-driehoek_Boven" ipt)
	(setvar "clayer" c1 )
	(reset)
    (princ)
  )

  (defun C:BInsertRevDriehoek2 ( / ipt c1)
	(initerr)  
	(setvar "cmdecho" 0)
	(setq ipt (getpoint "Geef insertiepunt: "))
	(setq c1 (getvar "clayer"))
    (princ "\n")
    (mfixLayer "0100-SYMBOOL-co-25" "7" "continuous" "default" 1 )
    (BInsertScaled "Revisie-driehoek_Onder" ipt)
	(setvar "clayer" c1 )
	(reset)	
    (princ)
  )
  
  (defun BInsertStramienaanduiding ( / ipt c1)
	(initerr)  
	(setvar "cmdecho" 0)
	(setq c1 (getvar "clayer"))
    (princ "\n")
	(L12_standard_BInsertStramienaanduiding)
    (L12_BInsertScLa "Stramienaanduiding-")
	(setvar "clayer" c1 )
	(reset)	
    (princ)
  )
  
 (defun L12_BInsertSections (blockname / ipt c1 blockname)
	(initerr)  
	(setvar "cmdecho" 0)
	(setq c1 (getvar "clayer"))
    (princ "\n")
	(L12_standard_BInsertStramienaanduiding)
    (L12_BInsertSc blockname)
	(setvar "clayer" c1 )
	(reset)	
    (princ)
 )


;;-----[ Functies die kaders plaatst]-------------------

  (defun Kader (kader / ipt c1)
	(L12_checkinstel)
    (setq ipt (list 0 0 0 ))
	(setq c1 (getvar "clayer"))
	(L12_standard_kader)
    (command "._ZOOM" "e")
	(setvar "clayer" c1 )
    (princ)
  )



;;-----[ Functies die stempels plaatsen]----------------------

(defun Stempel_NL (stempel / ipt c1)
  (setq c1 (getvar "clayer"))
  (setq ipt (getpoint "Geef insertiepunt: "))
  (mfixLayer "0100-SYMBOOL-co-25" "7" "continuous" "default" 1 )
  (BInsertScaled stempel ipt)
  (setvar "clayer" c1 )
  (princ)
)

(defun Stempel_UK (stempel / ipt c1 )
  (setq c1 (getvar "clayer"))
  (setq ipt (getpoint "Geef insertiepunt: "))
  (mfixLayer "0100-SYMBOOL-co-25" "7" "continuous" "default" 1 )
  (BInsertScaled stempel ipt)
  (setvar "clayer" c1 )
  (princ)
)

;;-----[ Functie die block inlaad]----------------------------kan dit niet korter?????

  (defun GetBlockDef ( strBlock / le )
    (if (= (tblsearch "BLOCK" strblock) nil)
      (progn
        (if (= (findfile (strcat strblock ".dwg")) nil)
        (progn
	      (textscr)
          (getstring (strcat "Kan block '" strBlock "' niet vinden."))
        )
      (progn
          (command "insert" strBlock  "0,0,0" "1" "1" "0")
          (setq le (ssname (ssget "L") 0))
	  (if (and (= (cdr (assoc 0 (entget le))) "INSERT")
        	   (= (strcase (cdr (assoc 2 (entget le)))) (strcase strBlock))
	      )
	     (progn
	        (command "ERASE" "LAST" "")
	     )
	  )
	)
      )
    )
  )
(princ)
)

(defun L12_BlTest (BlockName)
  (cdr
    (assoc 281
	   (entget (cdr (assoc 330 (entget (tblobjname "BLOCK" BlockName))))
	   )
    )
  )
)
