(DEFUN C:PLAATRIB ()

  (defun p:ERROR (st)
    (setvar "CMDECHO" cmde)
    (setvar "BLIPMODE" blip)
    (command "LAYER" "s" c1 "")
    (setvar "HIGHLIGHT" hlg)
    (setq *error* o:error)
    (prin1)
  )
  (setq	o:error	*error*
	*error*	p:error
  )
  (setq cmde (getvar "CMDECHO"))
  (setq blip (getvar "BLIPMODE"))
  (setq hlg (getvar "HIGHLIGHT"))
  (setq c1 (getvar "CLAYER"))
  (setvar "CMDECHO" 0)
  (setvar "BLIPMODE" 0)
  (setvar "HIGHLIGHT" 0)
  (graphscr)
  (command "LAYER" "m" "16---0--FUNDERING" "")
  (setq e1 (getpoint "\nGeef midden aan: "))
  (setq a1 (getdist e1 "\nGeef aanlegbreedte: "))
  (setq e (polar e1 pi (/ a1 2)))
  (setq e2 (polar e1 0 (/ a1 2)))
  (command "PLINE" e e2)
  (setq a2 (getdist e2 "\nGeef hoogte plaat: "))
  (setq e3 (polar e2 (* pi 0.5) a2))
  (command e3)
  (setq a3 (getdist e3 "\nGeef breedte rib: "))
  (setq e4 (polar e3 pi (/ (- a1 a3) 2)))
  (command e4)
  (setq a4 (getdist e4 "\nGeef hoogte rib: "))
  (setq e5 (polar e4 (* pi 0.5) a4))
  (setq e6 (polar e5 pi a3))
  (setq e7 (polar e6 (* pi 1.5) a4))
  (setq e8 (polar e (* pi 0.5) a2))
  (command e5 e6 e7 e8 "c")
  (command "LAYER" "s" c1 "")
  (setvar "CMDECHO" cmde)
  (setvar "BLIPMODE" blip)
  (setvar "HIGHLIGHT" hlg)
  (setq *error* o:error)
  (prin1)
)
(setq gbadeel '(p:error c:plaatrib))
(princ)
