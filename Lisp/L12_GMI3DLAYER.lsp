(prompt "\nCreatie van de 3D SWECO layers\n")
(defun C:L12_GMI3DLAYER ( / )
;	ALGEMEEN
(setvar "cmdecho" 0)
   (princ "\nLayers ALGEMEEN...")
      (command "-layer" "M" "AC-0000-AFBRAAK-co-12" "C" "3" "" "Lt" "continuous" "" "")
      (command "-layer" "M" "AC-0000-HULPLIJN-co-bruin"  "C" "36" "" "Lt" "continuous" "" "plot" "n"  "" "")
      (command "-layer" "M" "AC-0000-VIEW-co-06"  "C" "1" "" "Lt" "continuous" "" "plot" "n"  "" "")
      (command "-layer" "M" "AC-0000-ALGEMEEN-co-25" "C" "7" "" "Lt" "continuous" "" "")
      (command "-layer" "M" "AC-0000-ILLUSTRATIE-co-06" "C" "1" "" "Lt" "continuous" "" "")
      (command "-layer" "M" "AC-0100-SYMBOOL-co-25" "C" "7" "" "Lt" "continuous" "" "")
      (command "-layer" "M" "AC-0200-MAAT" "C" "7" "" "Lt" "continuous" "" "")
      (command "-layer" "M" "AC-0300-TEKST-25" "C" "7" "" "Lt" "continuous" "" "")
      (command "-layer" "M" "AC-0300-TEKST-35" "C" "2" "" "Lt" "continuous" "" "")
      (command "-layer" "M" "AC-0300-TEKST-50" "C" "6" "" "Lt" "continuous" "" "")
      (command "-layer" "M" "AC-0300-TEKST-70" "C" "4" "" "Lt" "continuous" "" "")
      (command "-layer" "M" "AC-0400-SCOPE-co-50" "C" "6" "" "Lt" "continuous" "" "")
      (command "-layer" "M" "AC-0500-ARCERING-06" "C" "1" "" "Lt" "continuous" "" "")
      (command "-layer" "M" "AC-0500-ARCERING-12" "C" "3" "" "Lt" "continuous" "" "")
      (command "-layer" "M" "AC-0500-ARCERING-grijs" "C" "9" "" "Lt" "continuous" "" "")
      (command "-layer" "M" "AC-0500-ARCERING-OMTREK-co-06"  "C" "1" "" "Lt" "continuous" "" "plot" "n"  "" "")
      (command "-layer" "M" "AC-0600-ASLIJN-dd-06" "C" "1" "" "Lt" "dashdot" "" "")
      (command "-layer" "M" "AC-0600-ASLIJN-dd-12" "C" "3" "" "Lt" "dashdot" "" "")
;	CONCRETE
   (princ "\nLayers CONCRETE...")
      (command "-layer" "M" "CONCRETE_BEAM" "C" "161" "" "Lt" "continuous" "" "")
      (command "-layer" "M" "CONCRETE_COLUMN" "C" "161" "" "Lt" "continuous" "" "")
      (command "-layer" "M" "CONCRETE_CURB" "C" "155" "" "Lt" "continuous" "" "")
      (command "-layer" "M" "CONCRETE_FLOOR" "C" "163" "" "Lt" "continuous" "" "")
      (command "-layer" "M" "CONCRETE_FOUNDATION" "C" "165" "" "Lt" "continuous" "" "")
      (command "-layer" "M" "CONCRETE_PILE" "C" "167" "" "Lt" "continuous" "" "")
      (command "-layer" "M" "CONCRETE_PLINTH" "C" "153" "" "Lt" "continuous" "" "")
      (command "-layer" "M" "CONCRETE_WALL" "C" "155" "" "Lt" "continuous" "" "")
;	Demolition
   (princ "\nLayers DEMOLITION...")
      (command "-layer" "M" "DEMO" "C" "51" "" "Lt" "hidden2" "" "")
      (command "-layer" "M" "DEMO_INSTR" "C" "237" "" "Lt" "continuous" "" "")
      (command "-layer" "M" "DEMO_POWER" "C" "237" "" "Lt" "continuous" "" "")
;	EQUIPEMENT
   (princ "\nLayers EQUIPEMENT...")
      (command "-layer" "M" "EQUIP_DEF" "C" "22" "" "Lt" "continuous" "" "")
      (command "-layer" "M" "EQUIP_DEFIN" "C" "22" "" "Lt" "continuous" "" "")
      (command "-layer" "M" "EQUIP_INSULATION" "C" "63" "" "Lt" "continuous" "" "")
      (command "-layer" "M" "EQUIP_PRELIM" "C" "86" "" "Lt" "continuous" "" "")
;	INFRASTRUCTUUR
   (princ "\nLayers EXISTING...")
      (command "-layer" "M" "EXIST" "C" "251" "" "Lt" "continuous" "" "")
      (command "-layer" "M" "EXIST_EQUIP" "C" "252" "" "Lt" "continuous" "" "")
      (command "-layer" "M" "EXIST_INSTR" "C" "201" "" "Lt" "continuous" "" "")
      (command "-layer" "M" "EXIST_POWER" "C" "201" "" "Lt" "continuous" "" "")
      (command "-layer" "M" "EXIST_STEEL" "C" "251" "" "Lt" "continuous" "" "")
      (command "-layer" "M" "EXIST_SUPPORT" "C" "251" "" "Lt" "continuous" "" "")
;	STEEL
   (princ "\nLayers STEEL...")
      (command "-layer" "M" "STEEL_NEW" "C" "92" "" "Lt" "continuous" "" "")
	  (command "-layer" "M" "STEEL_NEW_RVS" "C" "152" "" "Lt" "continuous" "" "")
      (command "-layer" "M" "STEEL_PLATE" "C" "30" "" "Lt" "continuous" "" "")
      (command "-layer" "M" "STEEL_RAILING" "C" "43" "" "Lt" "continuous" "" "")
      (command "-layer" "M" "STEEL_LADDER" "C" "43" "" "Lt" "continuous" "" "")
      (command "-layer" "M" "STEEL_MONORAIL" "C" "52" "" "Lt" "continuous" "" "")
      (command "-layer" "M" "STEEL_SUPPORT" "C" "212" "" "Lt" "continuous" "" "")
;	HVAC
   (princ "\nLayers HVAC...")
      (command "-layer" "M" "HVAC_CONDENSAAT" "C" "160" "" "Lt" "continuous" "" "")
      (command "-layer" "M" "HVAC_EQUIPMENT" "C" "121" "" "Lt" "continuous" "" "")
      (command "-layer" "M" "HVAC_EXTRACTIE" "C" "200" "" "Lt" "continuous" "" "")
      (command "-layer" "M" "HVAC_EXTRACTIE_PR" "C" "202" "" "Lt" "continuous" "" "")
      (command "-layer" "M" "HVAC_GAS" "C" "61" "" "Lt" "continuous" "" "")
      (command "-layer" "M" "HVAC_KOELWATER" "C" "140" "" "Lt" "continuous" "" "")
      (command "-layer" "M" "HVAC_PULSIE" "C" "100" "" "Lt" "continuous" "" "")
      (command "-layer" "M" "HVAC_PULSIE_PR" "C" "82" "" "Lt" "continuous" "" "")
      (command "-layer" "M" "HVAC_VERWARMINGSWATER" "C" "20" "" "Lt" "continuous" "" "")
;	VARIA
   (princ "\nLayers VARIA...")
      (command "-layer" "M" "FREE ZONE" "C" "40" "" "Lt" "continuous" "" "")
      (command "-layer" "M" "NEW_INSTR" "C" "13" "" "Lt" "continuous" "" "")
      (command "-layer" "M" "NEW_POWER" "C" "94" "" "Lt" "continuous" "" "")
      (command "-layer" "M" "REUSE" "C" "132" "" "Lt" "continuous" "" "")
      (command "-layer" "M" "SPS-XXX" "C" "212" "" "Lt" "continuous" "" "")
      (command "-layer" "M" "TITEL" "C" "7" "" "Lt" "continuous" "" "")
      (command "-layer" "M" "LAYER_1" "C" "160" "" "Lt" "continuous" "" "")
      (command "-layer" "M" "VIEW"  "C" "12" "" "Lt" "continuous" "" "plot" "n"  "" "")
   (Princ "\nLayerset is aangemaakt.")
   (setvar "CLAYER" "AC-0000-ALGEMEEN-co-25")
  (princ)
)
