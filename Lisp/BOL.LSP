(defun c:bol (/ spoed diameter lengte dot dot2 temp aantbol teller x1 y1 xc yc xd yd hoek osv pt1 pt2)

(setq schaal (L12_getschaal))
(setvar "cmdecho" 0)

(setq pt1 (getpoint "  Startpunt van de lijn "))
(princ "\n ")
(setq pt2 (getpoint pt1 " Eindpunt van de lijn "))
(princ "\n ")
(initget (+ 1 2 4))
(setq BS (getint "\nGeef de schaal van de doorsnede: "))
(setq	SF  (/ schaal BS))
(initget (+ 1 2 4))
(setq spoed (getreal " Geef spoed "))
(princ "\n ")
(initget (+ 1 2 4))
(setq diameter (getreal " Geef diameter "))
(princ "\n ")
(while (<= spoed diameter)
	(princ "De spoed moet groter zijn dan de diameter!\n ")
	(initget (+ 1 2 4))
	(setq spoed (getreal " Geef spoed (tussenafstand) "))
	(princ "\n ")
	(initget (+ 1 2 4))
	(setq diameter (getreal " Geef staafdiameter "))
	(princ "\n ")
)
(setq osv (getvar "osmode"))
(setvar "osmode" 0)
(setq hoek (angle pt1 pt2))
(setq lengte (distance pt1 pt2))
(setq dot (* SF (fix (sqrt (* diameter 10))) 2 ))
(setq dot2 (* dot 0.5))
(setq temp (/ lengte spoed))
(setq aantbol (+ (fix temp) 1))
(setq teller 1)
(setq x1 (car pt1))
(setq y1 (cadr pt1))
(setq xc (+ x1 dot2))
(setq yc (+ y1 dot2))
(command "donut" 0 dot (list xc yc) "")
(while (< teller aantbol)
	(setq xd (+ xc (* spoed (cos hoek))))
	(setq yd (+ yc (* spoed (sin hoek))))
	(command "donut" 0 dot (list xd yd) "")
	(setq xc xd)
	(setq yc yd)
	(setq teller (+ teller 1))
)
(setvar "cmdecho" 1)
(setvar "osmode" osv)
(princ "\nAantal staven :")
(prin1 aantbol)
(princ)
)
